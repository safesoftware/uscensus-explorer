FME workspace uscensus.fmw

Parameters:
- GEOM = [{"type":"Feature","properties":{},"geometry":{"type":"Point","coordinates":[-115.18890380859376,39.37889504706486]}}]
- FME_SERVER_DEST_DIR = $(FME_SHAREDRESOURCE_DATA)/census_data   # FME Server Destination Directory

Writers:
- GEOJSON_1: GEOJSON to $(FME_SHAREDRESOURCE_DATA)/blockgroups.json

Creator
    COORDSYS = LL84
    GEOMTYPE = Geometry Object
    NUM = 1
    CREATED -> ParameterFetcher
ParameterFetcher
    ATTR_LIST = _GEOM $(GEOM)
    -> JSONFragmenter
JSONFragmenter
    EXPLODE_FORMAT = GEOJSON
    EXTRACT_ATTR = No
    JSON_ATTR = _GEOM
    JSON_QUERY = json[*]
    READ_FROM_FILE = NO
    REJECT_EMPTY_LISTS = YES
    FRAGMENTS -> SimpleUSCensusCaller [Points]
SimpleUSCensusCaller: USCensusCaller
    Areas -> blockgroups (writer GEOJSON_1)
blockgroups (writer GEOJSON_1)
    attributes: Total Population int, Females int, Males int, Hispanic int, Hawaiian int, Caucasian int, Native American int, Black or African American int, Asian int, Other Ethnicity int, Under 5 int, 5 to 17 int, 18 to 24 int, 25 to 44 int, 45 to 64 int, 65 or Over int, Total Housing Units int, Owner Occupied int, Renter Occupied int, Average Household Occupancy float, Total Vacant Units int, Median Home Value string, Median Household Income string, Population Below Poverty Level int, Population Without Health Insurance int, Population Without High School Diploma int, Population With College Credential int, State string, Census Tract int, Census Block Group int,
      GEOID int, Area (sq. mi.) float

FME custom transformer USCensusCaller
USCensusCaller Transformer
Enhance your workflow by connecting to the US Census API and extracting demographic data. 
Overview
The USCensusCaller pulls from the US Census Bureau's 2016 Planning Database and accesses data collected by either the US Census or the American Community Survey. 
A TIGERWeb call is also built in, allowing the non-spatial Census data to be merged with the appropriate block group polygon representing the data's spatial extent. This allows for visualization on top of any further analysis on the census data.
Inputs/Outputs
Input:  Geocoded point data in the LL84 coordinate system (lat/long).
Output:  Census Block Group areas (that intersect your inputs) with demographic attributes. The input point data in the appropriate US Census coordinate system.
Parameters
Data Source: The 2016 planning database hosts two datasets: the American Community Survey and the US Census. While these datasets overlap, they contain different variables and are administered to different subsets of the American population, resulting in different values. 
In order to minimize the number of variables called at once, please choose one or the other when using the USCensusCaller. The American Community Survey is suggested for economic data, while the Us Census dataset has more specific data concerning demographics and population.
API Key: While an API key is not needed to access the planning database, it is recommended for large or repetitive calls, as a limit based on IP address does exist. Consider requesting a key here.
External documentation:
-US Census Bureau Planning Database
-List of variables available through the API

Parameters:
- APIkey =   # API Key

Points (input)
    -> CoordinateExtractor
Areas (output)

Bookmark: Reproject Incoming Data
CoordinateExtractor
    LIST_NAME = _indices
    MODE = All Coordinates
    -> VertexCreator
VertexCreator
    MEASURE_TYPE = Continuous
    MISSING_VAL_MODE = None (Drop Values)
    MODE_NAME = Add Point
    XVAL = @Value(_indices{0}.x)
    YVAL = @Value(_indices{0}.y)
    -> CsmapReprojector
CsmapReprojector
    DEST = EPSG:3857
    INTERPOLATION_TYPE_NAME = Nearest Neighbor
    RASTER_CELL_SIZE = Preserve Cells
    RASTER_TOLERANCE = 0.0
    VERTICAL_HANDLING = Ignore heights and leave them unchanged
    REPROJECTED -> CoordinateConcatenator
CoordinateConcatenator
    COORDINATES_TO_INCLUDE_DIS = Y X
    COORD_ATTR = _coordinates
    COORD_DELIM = |
    ELEMENT_DELIM = ,
    -> AttributeCreator

Bookmark: TIGERWeb Call (Spatial)
AttributeCreator
    ATTR_TABLE = SET_TO url = https://tigerweb.geo.census.gov/arcgis/rest/services/Generalized_ACS2016/Tracts_Blocks/MapServer/4/query?where=1%3D1&geometry=@Value(_coordinates)&geometryType=esriGeometryPoint&inSR=esriSpatialRelIntersects&outFields=*&returnGeometry=true&returnTrueCurves=false&returnIdsOnly=false&returnCountOnly=false&returnZ=false&returnM=false&returnDistinctValues=false&f=geojson
    -> FeatureReader [INITIATOR]
FeatureReader
    ATTRS_TO_EXPOSE = STATE COUNTY TRACT BLKGRP
    ATTR_ACCUM_MODE = Only Use Result
    COMBINE_GEOM = Use Result
    DATASET = @Value(url)
    FORMAT = GEOJSON
    GEOJSON_FLATTEN_MODE = ALL_LEVELS
    GEOJSON_USE_BASENAME_AS_DEFAULT_FEATURE_TYPE = Yes
    GEOJSON_USE_SEARCH_ENVELOPE = NO
    INTERACT = <No Spatial Filter>
    OUTPUT_FEATURES_DISPLAY = Schema and Data Features
    <OTHER> -> Dissolver

Bookmark: US Census Planning Database Call
Dissolver
    ACCUM_INPUT_ATTRS = Use Attributes From One Feature
    CLEANING_TOLERANCE = None
    CONNECT_Z_MODE = First Wins
    DEAGGREGATE_INPUT = Yes
    GROUP_BY = BLKGRP TRACT
    NO_OVRLP = No
    PROPER_NODED = No
    AREA -> AttributeCreator_2
AttributeCreator_2
    ATTR_TABLE = SET_TO url2 = https://api.census.gov/data/2016/pdb/blockgroup?get=County_name,State_name,LAND_AREA,Block_Group,Tot_Population_ACS_10_14,Males_ACS_10_14,Females_ACS_10_14,Pop_65plus_ACS_10_14,Pop_under_5_ACS_10_14,Pop_5_17_ACS_10_14,Pop_18_24_ACS_10_14,Pop_25_44_ACS_10_14,Pop_45_64_ACS_10_14,Pop_65plus_ACS_10_14,NH_White_alone_ACS_10_14,NH_Blk_alone_ACS_10_14,NH_AIAN_alone_ACS_10_14,NH_Asian_alone_ACS_10_14,NH_NHOPI_alone_ACS_10_14,NH_SOR_alone_ACS_10_14,Hispanic_ACS_10_14,Tot_Housing_Units_ACS_10_14,Tot_Vacant_Units_ACS_10_14,Owner_Occp_HU_ACS_10_14,Renter_Occp_HU_ACS_10_14,Tot_Vacant_Units_ACS_10_14,avg_Tot_Prns_in_HHD_ACS_10_14,Med_HHD_Inc_BG_ACS_10_14,Prs_Blw_Pov_Lev_ACS_10_14,Med_House_Value_BG_ACS_10_14,Not_HS_Grad_ACS_10_14,College_ACS_10_14,No_Health_Ins_ACS_10_14&for=block+group:@Value(BLKGRP)&in=state:@Value(STATE)&in=county:@Value(COUNTY)&in=tract:@Value(TRACT)&key=$(APIkey)
    -> HTTPCaller_2
HTTPCaller_2
    CONNECTION_TIMEOUT_LENGTH = 60
    ERROR_ATTR = _error
    FOLLOW_REDIRECTS = Yes
    HTTP_METHOD = GET
    RESPONSE_HEADER_LIST_ATTR = _headers
    SAVE_FILE = Attribute
    STATUS_CODE_ATTR = _http_status_code
    TARGET_ATTR = _response_body
    TARGET_ATTR_ENCODING = auto-detect
    TARGET_URL = @Value(url2)
    TRANSFER_TIMEOUT_LENGTH = 90
    USE_COOKIES = No
    VERIFY_SSL_CERTIFICATES = Yes
    -> StringConcatenator
StringConcatenator
    ACTION = Create New Attribute
    PARM_LINE = @Value(STATE)@Value(COUNTY)@Value(TRACT)@Value(BLKGRP)
    VAL_ATTR = GEOID
    -> JSONExtractor

Bookmark: Parse JSON Response
JSONExtractor
    EXTRACT_QUERY_TABLE = attrnames json[0] attrvalues json[1]
    JSON_DOCUMENT = @Value(_response_body)
    READ_FROM_FILE = NO
    EVALUATED -> JSONFragmenter_4
JSONFragmenter_4
    EXPLODE_FORMAT = JSON
    EXTRACT_ATTR = Yes
    JSON_ATTR = attrnames
    JSON_QUERY = json[*]
    PREF_STRING = _attrnames
    READ_FROM_FILE = NO
    RECURSIVE = Yes
    REJECT_EMPTY_LISTS = YES
    FRAGMENTS -> JSONExtractor_2
JSONExtractor_2
    EXTRACT_QUERY_TABLE = attrvalues json[@Value(json_index)]
    JSON_DOCUMENT = @Value(attrvalues)
    READ_FROM_FILE = NO
    EVALUATED -> AttributeCreator_9

Bookmark: Formatting and Cleanup
AttributeCreator_9
    ATTR_TABLE = SET_TO @Value(attrnames) = @Value(attrvalues)
    -> Dissolver_2
Dissolver_2
    ACCUM_INPUT_ATTRS = Merge Incoming Attributes
    CLEANING_TOLERANCE = None
    CONNECT_Z_MODE = First Wins
    DEAGGREGATE_INPUT = Yes
    GROUP_BY = TRACT BLKGRP
    NO_OVRLP = No
    PROPER_NODED = No
    AREA -> AttributeManager_2
AttributeManager_2
    ATTR_TABLE:
      REMOVE attrnames
      REMOVE attrvalues
      REMOVE url2
      REMOVE STATE
      REMOVE COUNTY
      REMOVE _headers{}.name
      REMOVE _headers{}.value
      REMOVE _response_body
      REMOVE _http_status_code
      REMOVE json_type
      REMOVE json_index
    -> AttributeExposer
AttributeExposer
    ATTR_LIST = Pop_45_64_ACS_10_14,NH_AIAN_alone_ACS_10_14,Females_ACS_10_14,Pop_65plus_ACS_10_14,NH_Asian_alone_ACS_10_14,NH_SOR_alone_ACS_10_14,Hispanic_ACS_10_14,NH_White_alone_ACS_10_14,Pop_5_17_ACS_10_14,Med_HHD_Inc_BG_ACS_10_14,Pop_25_44_ACS_10_14,Tot_Vacant_Units_ACS_10_14,Tot_Housing_Units_ACS_10_14,No_Health_Ins_ACS_10_14,Pop_under_5_ACS_10_14,Prs_Blw_Pov_Lev_ACS_10_14,Not_HS_Grad_ACS_10_14,College_ACS_10_14,Pop_18_24_ACS_10_14,Owner_Occp_HU_ACS_10_14,Med_House_Value_BG_ACS_10_14,avg_Tot_Prns_in_HHD_ACS_10_14,Tot_Population_ACS_10_14,Pop_65plus_ACS_10_14,Tot_Vacant_Units_ACS_10_14,Males_ACS_10_14,Renter_Occp_HU_ACS_10_14,NH_NHOPI_alone_ACS_10_14,NH_Blk_alone_ACS_10_14,State_name,LAND_AREA
    -> AttributeRenamer
AttributeRenamer
    ATTR_TABLE:
      RENAME_SET_DEFAULT Tot_Population_ACS_10_14 > Total Population
      RENAME_SET_DEFAULT Females_ACS_10_14 > Females
      RENAME_SET_DEFAULT Males_ACS_10_14 > Males
      RENAME_SET_DEFAULT Hispanic_ACS_10_14 > Hispanic
      RENAME_SET_DEFAULT NH_NHOPI_alone_ACS_10_14 > Hawaiian
      RENAME_SET_DEFAULT NH_White_alone_ACS_10_14 > Caucasian
      RENAME_SET_DEFAULT NH_AIAN_alone_ACS_10_14 > Native American
      RENAME_SET_DEFAULT NH_Blk_alone_ACS_10_14 > Black or African American
      RENAME_SET_DEFAULT NH_Asian_alone_ACS_10_14 > Asian
      RENAME_SET_DEFAULT NH_SOR_alone_ACS_10_14 > Other Ethnicity
      RENAME_SET_DEFAULT Pop_under_5_ACS_10_14 > Under 5
      RENAME_SET_DEFAULT Pop_5_17_ACS_10_14 > 5 to 17
      RENAME_SET_DEFAULT Pop_18_24_ACS_10_14 > 18 to 24
      RENAME_SET_DEFAULT Pop_25_44_ACS_10_14 > 25 to 44
      RENAME_SET_DEFAULT Pop_45_64_ACS_10_14 > 45 to 64
      RENAME_SET_DEFAULT Pop_65plus_ACS_10_14 > 65 or Over
      RENAME_SET_DEFAULT Tot_Housing_Units_ACS_10_14 > Total Housing Units
      RENAME_SET_DEFAULT Owner_Occp_HU_ACS_10_14 > Owner Occupied
      RENAME_SET_DEFAULT Renter_Occp_HU_ACS_10_14 > Renter Occupied
      RENAME_SET_DEFAULT avg_Tot_Prns_in_HHD_ACS_10_14 > Average Household Occupancy
      RENAME_SET_DEFAULT Tot_Vacant_Units_ACS_10_14 > Total Vacant Units
      RENAME_SET_DEFAULT Med_House_Value_BG_ACS_10_14 > Median Home Value
      RENAME_SET_DEFAULT Med_HHD_Inc_BG_ACS_10_14 > Median Household Income
      RENAME_SET_DEFAULT Prs_Blw_Pov_Lev_ACS_10_14 > Population Below Poverty Level
      RENAME_SET_DEFAULT No_Health_Ins_ACS_10_14 > Population Without Health Insurance
      RENAME_SET_DEFAULT Not_HS_Grad_ACS_10_14 > Population Without High School Diploma
      RENAME_SET_DEFAULT College_ACS_10_14 > Population With College Credential
      RENAME_SET_DEFAULT State_name > State
      RENAME_SET_DEFAULT TRACT > Census Tract
      RENAME_SET_DEFAULT BLKGRP > Census Block Group
      RENAME_SET_DEFAULT GEOID
      RENAME_SET_DEFAULT LAND_AREA > Area (sq. mi.)
    -> Areas (output)
