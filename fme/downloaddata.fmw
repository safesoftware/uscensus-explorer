FME workspace downloaddata.fmw

Parameters:
- TEXT =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   # GEOM GEOM

Writers:
- CSV2_1: CSV2 to $(FME_SHAREDRESOURCE_TEMP)

Creator
    GEOMTYPE = Geometry Object
    NUM = 1
    CREATED -> ParameterFetcher
ParameterFetcher
    ATTR_LIST = _GEOM $(GEOM)
    -> JSONFragmenter
JSONFragmenter
    EXPLODE_FORMAT = GEOJSON
    EXTRACT_ATTR = Yes
    JSON_ATTR = _GEOM
    JSON_QUERY = json[*]
    NEW_ATTRIBUTES = Total Population Females Males Hispanic Hawaiian Caucasian Native American Black or African American Asian Other Ethnicity Under 5 5 to 17 18 to 24 25 to 44 45 to 64 65 or Over Total Housing Units Owner Occupied Renter Occupied Average Household Occupancy Total Vacant Units Median Home Value Median Household Income Population Below Poverty Level Population Without Health Insurance Population Without High School Diploma Population With College Credential State Census Tract Census Block Group GEOID Area (sq. mi.)
    READ_FROM_FILE = NO
    RECURSIVE = Yes
    REJECT_EMPTY_LISTS = YES
    FRAGMENTS -> blockgroups (writer CSV2_1)
blockgroups (writer CSV2_1)
    attributes: Total Population string, Females string, Males string, Hispanic string, Hawaiian string, Caucasian string, Native American string, Black or African American string, Asian string, Other Ethnicity string, Under 5 string, 5 to 17 string, 18 to 24 string, 25 to 44 string, 45 to 64 string, 65 or Over string, Total Housing Units string, Owner Occupied string, Renter Occupied string, Average Household Occupancy string, Total Vacant Units string, Median Home Value string, Median Household Income string, Population Below Poverty Level string, Population Without Health Insurance string, Population Without High School Diploma string, Population With College Credential string, State string, Census Tract string, Census Block Group string,
      GEOID string, Area (sq. mi.) string
